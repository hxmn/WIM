FME workspace well_node_conversion_TEST.fmw
Startup Python:
      import fmeobjects
      import cx_Oracle

      db_env = FME_MacroValues['TARGET_ENVIRONMENT']
      db_user = FME_MacroValues['FME_USERNAME']
      db_pwd = FME_MacroValues['FME_PWD']

      logger = fmeobjects.FMELogFile()
      con = cx_Oracle.connect(db_user + '/' + db_pwd + '@' + db_env)

      logger.logMessageString('Connecting to ' + db_env + ' as ' + db_user, fmeobjects.FME_INFORM)

      cur = con.cursor()
      cur.callproc('wim.nad27_generator.fme_cleanup')
      cur.close()

      con.close()
Shutdown Python:
      import fmeobjects
      import cx_Oracle

      db_env = FME_MacroValues['TARGET_ENVIRONMENT']
      db_user = FME_MacroValues['FME_USERNAME']
      db_pwd = FME_MacroValues['FME_PWD']

      logger = fmeobjects.FMELogFile()
      con = cx_Oracle.connect(db_user + '/' + db_pwd + '@' + db_env)

      logger.logMessageString('Connecting to ' + db_env + ' as ' + db_user, fmeobjects.FME_INFORM)

      cur = con.cursor()
      cur.callproc('wim.nad27_generator.load_fme_converted')
      cur.close()

      con.close()

Parameters:
- SourceDataset_GEODATABASE_SDE = sde   # Source Esri ArcSDE Geodatabase Dataset
- ROW_CHANGED_BY = GIS
- SPATIAL_CHECK_FC_INSTANCE = sde:oracle11g:tlmgist:sde_global
- SPATIAL_CHECK_FC_VERSION = SDE_GLOBAL.DEFAULT
- SPATIAL_CHECK_FC_USERNAME = GIS_APP_VIEWER
- SPATIAL_CHECK_FC_PWD =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
- SPATIAL_CHECK_FC_SERVER = TLMGIST
- TARGET_ENVIRONMENT = PETTEST
- FME_USERNAME = FME
- FME_PWD = winter3

Readers:
- GEODATABASE_SDE_1: GEODATABASE_SDE from $(SourceDataset_GEODATABASE_SDE)

Writers:
- ORACLE8I_DB_1: ORACLE8I_DB to $(TARGET_ENVIRONMENT)

GIS_IHS.OFF_COUNTRIES (reader GEODATABASE_SDE_1)
    attributes: geodb_oid integer, IHS_ID double, REGION_NAME char(50), REGION_ID double, COUNTRY_NAME char(50), FORMER_COUNTRY_NAME char(50), FORMER_COUNTRY_ID double, ISO_COUNTRY_NAME char(50), ISO_COUNTRY_ID char(4), GEN_TYP char(255), STAT_TYP char(255), ONS_OFF_ID char(3), IRIS_CTRY_ID char(4), DATUM_ID char(3), DATUM_TRFM_ID char(10), GRAPHIC_ENTRY date, GRAPHIC_UPD date, DATA_UPD date, IRIS_DATA_UPD date, AREA_VALUE double, AREA_MEAS_UNIT char(4), DATA_SET char(255), OBJECTID integer, SHAPE.AREA double, SHAPE.LEN double
    -> AttributeKeeper
GIS_IHS.ONS_COUNTRIES (reader GEODATABASE_SDE_1)
    attributes: geodb_oid integer, IHS_ID double, REGION_NAME char(50), REGION_ID double, COUNTRY_NAME char(50), FORMER_COUNTRY_NAME char(50), FORMER_COUNTRY_ID double, ISO_COUNTRY_NAME char(50), ISO_COUNTRY_ID char(4), GEN_TYP char(255), STAT_TYP char(255), ONS_OFF_ID char(3), IRIS_CTRY_ID char(4), DATUM_ID char(3), DATUM_TRFM_ID char(10), GRAPHIC_ENTRY date, GRAPHIC_UPD date, DATA_UPD date, IRIS_DATA_UPD date, AREA_VALUE double, AREA_MEAS_UNIT char(4), DATA_SET char(255), OBJECTID integer, SHAPE.AREA double, SHAPE.LEN double
    -> AttributeKeeper
Note: Keep the Country Name / attribute
AttributeKeeper
    KEEP_ATTRS = COUNTRY_NAME
    -> SpatialFilter_2 [input 1]
SQLCreator
    ORACLE8I_DB_USER_NAME = WIM
    ORACLE8I_DB_SHOW_SYSTEM_TABLES = NO
    ORACLE8I_DB_PASSWORD = winter3
    SQL_STATEMENT:
      select ipl_uwi, node_id, source, geog_coord_system_id, location_qualifier, node_obs_no, node_position, country, province_state
          , latitude, longitude
          , '4267' as target_geog_coord_system_id, row_changed_by, row_changed_date, user as row_created_by, sysdate as row_created_date, remark
          , null as target_latitude, null as target_longitude
      from wim.wim_nad27_conv_stage_vw
      where nad_type = 'NEW'
    EXPOSED_ATTRIBUTE_LIST = COUNTRY,GEOG_COORD_SYSTEM_ID,IPL_UWI,LATITUDE,LOCATION_QUALIFIER,LONGITUDE,NODE_ID,NODE_OBS_NO,NODE_POSITION,PROVINCE_STATE,REMARK,ROW_CHANGED_BY,ROW_CHANGED_DATE,ROW_CHANGED_DATE.full,ROW_CREATED_BY,ROW_CREATED_DATE,ROW_CREATED_DATE.full,SOURCE,TARGET_GEOG_COORD_SYSTEM_ID,TARGET_LATITUDE,TARGET_LONGITUDE
    ORACLE8I_DB_SERVER_TYPE = ORACLE8i
    DATASET = PETTEST
    ORACLE8I_DB_REMOVE_SCHEMA_QUALIFIER = NO
    ORACLE8I_DB_PERSISTENT_CONNECTION = NO
    FORMAT = ORACLE8I_DB
    RESULT -> 2DPointReplacer
Note: Spatialize the incoming / tabulated data
2DPointReplacer
    XVALATTR = @Value(LONGITUDE)
    YVALATTR = @Value(LATITUDE)
    POINT -> SpatialFilter_2 [input 2]
Note: Attach country attribute
SpatialFilter_2
    USE_BOUNDING_BOX = No
    MERGE_ATTRS = Yes
    BASE_TYPE = Multiple Bases
    PASS_CRITERIA = Pass Against One Base
    PREDATTR = _predicate
    PREDICATES = CONTAINS
    CURVE_BOUNDARY_RULE_PARAM = Default Rule
    PASSED -> TestFilter
    FAILED -> AttributeCreator_2
Note: Filter out Canada and USA points / with NAD83 and WGS84 EPSG codes
TestFilter
    TEST_LIST:
      BOOL_OP,AND,COMPOSITE_TEST,<Unused>,TEST_CLAUSE,"TEST @Value(GEOG_COORD_SYSTEM_ID) = 4269
      TEST @Value(COUNTRY_NAME) = Canada",Canada - 4269 - NAD83,BOOL_OP,AND,COMPOSITE_TEST,<Unused>,TEST_CLAUSE,"TEST @Value(GEOG_COORD_SYSTEM_ID) = 4326
      TEST @Value(COUNTRY_NAME) = Canada",Canada - 4326 - WGS84,BOOL_OP,AND,COMPOSITE_TEST,<Unused>,TEST_CLAUSE,"TEST @Value(GEOG_COORD_SYSTEM_ID) = 4269
      TEST @Value(COUNTRY_NAME) = United States",USA - 4269 - NAD83,BOOL_OP,AND,COMPOSITE_TEST,<Unused>,TEST_CLAUSE,"TEST @Value(GEOG_COORD_SYSTEM_ID) = 4326
      TEST @Value(COUNTRY_NAME) = United States",USA - 4326 - WGS84
    DEFAULT_VALUE = <UNFILTERED>
    <UNFILTERED> -> AttributeCreator_4
    USA - 4326 - WGS84 -> CsmapReprojector
    USA - 4269 - NAD83 -> CsmapReprojector
    Canada - 4326 - WGS84 -> CsmapReprojector_2
    Canada - 4269 - NAD83 -> CsmapReprojector_2
Note: Apply the NTv2 / transformation method
CsmapReprojector_2
    DEST = EPSG:4267
    RASTER_CELL_SIZE = Preserve Cells
    TRANSFORMATION = NAD27_to_NAD83_Canada_FME (Reversed)
    SOURCE = EPSG:4269
    INTERPOLATION_TYPE_NAME = Nearest Neighbor
    VERTICAL_HANDLING = Ignore heights and leave them unchanged
    REPROJECTED -> CoordinateExtractor
Note: Apply the NADCON / transformation method
CsmapReprojector
    DEST = EPSG:4267
    RASTER_CELL_SIZE = Preserve Cells
    TRANSFORMATION = NAD27_to_NAD83 (Reversed)
    SOURCE = EPSG:4269
    INTERPOLATION_TYPE_NAME = Nearest Neighbor
    VERTICAL_HANDLING = Ignore heights and leave them unchanged
    REPROJECTED -> CoordinateExtractor
Note: Pull transformed coordinate / values into NAD27_LONGITUDE / and NAD27_LATITUDE fields
CoordinateExtractor
    Y_ATTR = TARGET_LATITUDE
    X_ATTR = TARGET_LONGITUDE
    Z_DEFAULT = -9999
    Z_ATTR = _z
    IND = 0
    -> AttributeCreator
Note: Enter 4267 (NAD27) EPSG code / into the TARGET_GEOG_COORD_SYSTEM_ID / attribute
AttributeCreator
    ATTR_LIST = TARGET_GEOG_COORD_SYSTEM_ID,4267
    -> ROW_CREATED_DATE
Note: Error message: / "Unregistered Datum"
AttributeCreator_4
    ATTR_LIST = REMARK,Unregistered Datum
    -> ROW_CREATED_DATE
Note: Error message: / "Out of bounds"
AttributeCreator_2
    ATTR_LIST = REMARK,Out of bounds
    -> ROW_CREATED_DATE
Note: ROW_CREATED_DATE [TimeStamper] / Time Stamp Format: FME Date/Time (^Y^m^d^H^M^S) / Time Stamp Attribute: ROW_CREATED_DATE
ROW_CREATED_DATE: TimeStamper
    FMT = FME Date/Time (^Y^m^d^H^M^S)
    TIME_ATTR = ROW_CREATED_DATE
    -> AttributeCreator_5
Note: Populate created by / attribute
AttributeCreator_5
    ATTR_LIST = ROW_CREATED_BY,$(ROW_CHANGED_BY)
    -> AttributeRenamer
AttributeRenamer
    ATTR_LIST = LATITUDE,LATITUDE,"",LONGITUDE,LONGITUDE,"",GEOG_COORD_SYSTEM_ID,GEOG_COORD_SYSTEM_ID,"",NODE_POSITION,NODE_POSITION,""
    -> FME.WELL_NODE_CONVERSION (writer ORACLE8I_DB_1)
Note: FME.WELL_NODE_CONVERSION: PETTEST [ORACLE8I_DB] (1)
FME.WELL_NODE_CONVERSION (writer ORACLE8I_DB_1)
    attributes: IPL_UWI varchar2(20), NODE_ID varchar2(20), SOURCE varchar2(20), GEOG_COORD_SYSTEM_ID varchar2(20), LOCATION_QUALIFIER varchar2(20), NODE_OBS_NO number(8,0), NODE_POSITION varchar2(1), COUNTRY varchar2(20), PROVINCE_STATE varchar2(20), LATITUDE number(12,7), LONGITUDE number(12,7), TARGET_GEOG_COORD_SYSTEM_ID varchar2(20), TARGET_LATITUDE number(12,7), TARGET_LONGITUDE number(12,7), REMARK varchar2(2000), ROW_CHANGED_BY varchar2(20), ROW_CHANGED_DATE date, ROW_CREATED_BY varchar2(30), ROW_CREATED_DATE date
